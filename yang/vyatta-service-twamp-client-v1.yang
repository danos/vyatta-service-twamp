module vyatta-service-twamp-client-v1 {
	namespace "urn:vyatta.com:mgmt:vyatta-service-twamp-client:1";
	prefix vyatta-service-twamp-client-v1;

	import ietf-inet-types {
		prefix inet;
	}
	import vyatta-types-v1 {
		prefix types;
	}
	import configd-v1 {
		prefix configd;
	}

	organization "AT&T Inc.";
	contact
		"AT&T
		 Postal: 208 S. Akard Street
				 Dallas, TX 75202
		 Web: www.att.com";

	description
		"Copyright (c) 2019 AT&T Intellectual Property
		 All rights reserved.

		 Copyright (c) 2017 by Brocade Communications Systems, Inc.
		 All rights reserved.

		 Redistribution and use in source and binary forms, with or without
		 modification, are permitted provided that the following conditions
		 are met:

		   1. Redistributions of source code must retain the above copyright
			  notice, this list of conditions and the following disclaimer.
		   2. Redistributions in binary form must reproduce the above
			  copyright notice, this list of conditions and the following
			  disclaimer in the documentation and/or other materials provided
			  with the distribution.
		   3. Neither the name of the copyright holder nor the names of its
			  contributors may be used to endorse or promote products derived
			  from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 TWAMP common client groupings and types";

	revision 2017-06-22 {
		description "Initial revision";
	}


	grouping twamp-client-padding {
		leaf padding {
			configd:help "Size of the padding to add to each test packet";
			description "Size of the padding to add to each test packet";
			type uint32 {
				range 0..65000;
			}
			units "bytes";
		}
	}

	grouping twamp-client-control-port {
		leaf control-port {
			configd:help "Port to be used for the server control connection";
			description "Port to be used for the server control connection";
			type inet:port-number {
				range 1..65535;
			}
			default 862;
		}
	}

	grouping twamp-client-interval {
		leaf interval {
			configd:help "Mean average time between each test packet sent";
			description "Mean average time between each test packet sent";
			type decimal64 {
				fraction-digits 12;
				range 0.0..max;
			}
			units "seconds";
		}
	}

	grouping twamp-client-port-range {
		container port-range {
			configd:help "The local port range to be used during tests";
			description "The local port range to be used during tests";
			must "start <= end" {
				error-message
					"port-range start must be lower than or equal to port-range end";
			}
			leaf start {
				configd:help "The lowest port number that can be used during tests";
				description "The lowest port number that can be used during the test";
				type inet:port-number {
					range 1..65535;
				}
				default 8760;
			}
			leaf end {
				configd:help "The highest port number that can be used during tests";
				description "The highest port number that can be used during the test";
				type inet:port-number {
					range 1..65535;
				}
				default 8960;
			}
		}
	}

	grouping twamp-client-source-address {
		leaf source-address {
			description
				"Source IP address to use for control and test packets.
				If an interface is specified, one of its addresses
				will be used.";
			configd:help "Source IP address for control and test packets";
			configd:allowed "vyatta-interfaces.pl --show all";
			type union {
				type types:ip-address;
				type types:interface-ifname;
			}
		}
	}

	grouping twamp-client-interface {
		leaf interface {
			description
				"Interface to use for control and test sessions.
				There must be a route to the server via the specified
				interface, and packets from the server to the client must
				be received on this interface.";
			configd:help "Interface for control and test sessions";
			configd:allowed "vyatta-interfaces.pl --show all";
			type types:interface-ifname;
		}
	}
}
