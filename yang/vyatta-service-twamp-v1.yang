module vyatta-service-twamp-v1 {
	namespace "urn:vyatta.com:mgmt:vyatta-service-twamp:1";
	prefix vyatta-service-twamp-v1;

	import ietf-inet-types {
		prefix inet;
	}

	import vyatta-types-v1 {
		prefix types;
	}
	import vyatta-services-v1 {
		prefix service;
	}
	import configd-v1 {
		prefix configd;
	}
	import ietf-yang-types {
		prefix ietf;
	}
	import vyatta-service-twamp-client-v1 {
		prefix twamp-client;
	}

	organization "AT&T Inc.";
	contact
		"AT&T
		 Postal: 208 S. Akard Street
				 Dallas, TX 75202
		 Web: www.att.com";

	description
		"Copyright (c) 2017-2021 AT&T Intellectual Property
		 All rights reserved.

		 Copyright (c) 2015-2017 by Brocade Communications Systems, Inc.
		 All rights reserved.

		 Redistribution and use in source and binary forms, with or without
		 modification, are permitted provided that the following conditions
		 are met:

		   1. Redistributions of source code must retain the above copyright
			  notice, this list of conditions and the following disclaimer.
		   2. Redistributions in binary form must reproduce the above
			  copyright notice, this list of conditions and the following
			  disclaimer in the documentation and/or other materials provided
			  with the distribution.
		   3. Neither the name of the copyright holder nor the names of its
			  contributors may be used to endorse or promote products derived
			  from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 TWAMP server configuration and twping RPC.";

	revision 2021-06-02 {
		description "Add no-offload option to server.";
	}
	revision 2020-01-20 {
		description "Increase maximum control sessions to 4096 per server.";
	}
	revision 2019-10-17 {
		description "Add must on password configuration leaf";
	}
	revision 2018-08-02 {
		description "Update description on pdv leaf";
	}
	revision 2017-12-15 {
		description "Add use-legacy-authentication leaf
			Move typedef and groupings from twping rpc scope to module scope";
	}
	revision 2017-06-22 {
		description "Use groupings from vyatta-service-twamp-client-v1
			Add source-address and interface input leaves to the twping RPC";
	}
	revision 2016-04-01 {
		description "Move TWAMP parameters to the twamp-parameters grouping";
	}
	revision 2016-01-07 {
		description "Add twping rpc.";
	}
	revision 2015-08-14 {
		description "Initial revision of version 1.";
	}

	typedef session-num {
		type uint16 {
			range 1..64;
		}
	}

	typedef timeout {
		type uint16 {
			range 1..3600;
		}
	}

	// Same as types:ip-prefix, but normalising the prefixes so
	// that they don't have addresses inconsistent with mask
	typedef ip-prefix {
		type union {
			type types:ipv4-prefix {
				configd:normalize "normalize ipv4-prefix";
			}
			type types:ipv6-prefix {
				configd:normalize "normalize ipv6-prefix";
			}
		}
	}

	typedef time-interval-ms {
		description "Floating point value representing a time interval";
		type decimal64 {
			fraction-digits 12;
		}
		units "milliseconds";
	}

	grouping min-max-time {
		leaf min {
			description "Minimum time observed during the sample period";
			type time-interval-ms;
		}
		leaf max {
			description "Maximum time observed during the sample period";
			type time-interval-ms;
		}
	}

	grouping addr-port {
		leaf address {
			description "IP address or domain name";
			type union {
				type types:ip-address;
				type types:domain-name;
			}
		}
		leaf port {
			description "Port number";
			type inet:port-number;
		}
	}

	grouping time-stats {
		uses min-max-time;
		leaf median {
			description "Median time observed during the sample period";
			type time-interval-ms;
		}
		leaf error {
			description "Calculated error for timing values";
			type time-interval-ms;
		}
		leaf pdv {
			description "Packet Delay Variation (jitter)";
			type time-interval-ms;
		}
	}

	grouping hops {
		leaf diff-num-ttl {
			description "A count of how many different hop count values were observed during the test.";
			type uint32;
		}
		leaf min {
			description "Minimum number of hops taken by a test packet";
			type uint32;
		}
		leaf max {
			description "Maximum number of hops taken by a test packet";
			type uint32;
		}
	}


	rpc twping {
		description "Measure the round trip time using TWAMP";

		input {
			leaf host {
				description "IP address or domain name of the test reflector";
				type union {
					type types:ip-address;
					type types:domain-name;
				}
				mandatory true;
			}
			uses twamp-client:twamp-client-source-address;
			uses twamp-client:twamp-client-interface;
			leaf count {
				description "Number of test packets to send";
				type uint32 {
					range 1..1000;
				}
				default 100;
			}
			uses twamp-client:twamp-client-padding;
			leaf session-count {
				description "Number of test sessions to create and use";
				type uint32 {
					range 1..65535;
				}
				default 1;
			}
			leaf test-dscp-value {
				description "RFC 2474 style DSCP value for TOS byte in test packets";
				type uint32 {
					range 0..63;
				}
				default 0;
			}
			uses twamp-client:twamp-client-control-port;
			uses twamp-client:twamp-client-interval;
			uses twamp-client:twamp-client-port-range {
				refine port-range {
					must "(end - start + 1) >= ../session-count" {
						description
							"Each session uses a different port
							 number, therefore, there must be
							 at least as many available ports
							 in the port-range as sessions that
							 are going to be opened";
						error-message "Size of the port-range must be at least as large as session-count";
					}
				}
			}
			container authentication {
				presence "Enables authentication";
				leaf mode {
					description "Authentication mode";
					type enumeration {
						enum "authenticate";
						enum "encrypt";
						enum "mixed";
					}
					default "authenticate";
				}
				leaf user {
					description "User name";
					type string {
						length 1..16;
					}
					mandatory true;
				}
				leaf passphrase {
					description "Passphrase for user";
					type string {
						length 1..1024;
					}
					mandatory true;
				}
			}
		}

		output {
			list results {
				key sid;
				leaf sid {
					description "Session Identifier";
					type string;
				}
				container source {
					description "Source address that test packets originated from";
					uses addr-port;
				}
				container destination {
					description "Destination address of the test reflector";
					uses addr-port;
				}
				container packets {
					leaf time-of-first {
						description "Time that the first test packet was sent";
						type ietf:date-and-time;
					}
					leaf time-of-last {
						description "Time that the last test packet was sent";
						type ietf:date-and-time;
					}
					leaf num-pkts-sent {
						description "Number of test packets that were sent";
						type uint32;
					}
					leaf num-pkts-lost {
						description "Number of test packets that were lost";
						type uint32;
					}
					leaf send-duplicates {
						description "Number of duplicate test packets received by the reflector";
						type uint32;
					}
					leaf reflect-duplicates {
						description "Number of duplicate test packets received by the sender";
						type uint32;
					}
				}

				container round-trip-time {
					description "Total round trip time, from when the test packet is sent " +
						"from the test client, until it is received back from the reflector";
					uses time-stats;
				}

				container send-time {
					description "Wire time for test packets to go from sender to reflector";
					uses time-stats;
				}
				container reflect-time {
					description "Wire time for test packets to go from the reflector, back to the sender";
					uses time-stats;
				}
				container reflector-processing-time {
					description "Time taken to process test packets within the reflector";
					uses min-max-time;
				}
				container send-hops {
					description "Number of hops taken by the test packets going from the sender to the reflector.";
					uses hops;
				}
				container reflect-hops {
					description "Number of hops taken by the test packets going from the reflector back to the sender";
					uses hops;
				}
			}
		}
		configd:call-rpc "twamp-ping-rpc";
	}

	grouping twamp-parameters {
		container twamp {
			configd:help "Two-Way Active Measurement Protocol";
			
			container server {
				presence "Signifies the TWAMP server is enabled";
				configd:help "Server configuration";
				
				leaf-list client-list {
					type ip-prefix;
					configd:help "List of clients that can connect to the server, by default any clients";
				}
				
				leaf-list mode {
					type enumeration {
						enum "no-unauthenticated" {
							configd:help "Disable support for unauthenticated sessions";
						}
						enum "no-mixed" {
							configd:help "Disable support for mixed mode sessions";
						}
						enum "no-authenticated" {
							configd:help "Disable support for authenticated sessions";
						}
						enum "no-encrypted" {
							configd:help "Disable support for encrypted sessions";
						}
					}
					configd:help "TWAMP authentication mode, by default all modes available";
				}

				leaf use-legacy-authentication {
					description
						"In revisions of this module prior to 2017-11-08 user
						 credentials were generated differently and are not
						 compatible with the way credentials are now generated.

						 If this server must interact with older twping clients
						 from vRouter versions prior to 17.3.0 in the authenticated,
						 encrypted, or mixed modes this option should be enabled.
						 Current twping clients will then no longer be able to
						 authenticate to the server.

						 If this option is not enabled older clients will not
						 be able to authenticate using existing passphrases";
					configd:help "Use legacy user authentication method";
					type empty;
				}
				
				list user {
					key "name";
					leaf name {
						type string {
							length 1..16;
						}
						configd:help "User identity";
					}
					leaf password {
						type string {
							length 1..1024;
						}
						mandatory true;
						configd:help "Password used to derive AES key";
						configd:secret true;
						must 'current() != "********"' {
							error-message "Password must be re-entered for each user";
						}
					}
					configd:help "Configure user for mixed, authenticated and encrypted modes";
				}
				
				leaf maximum-connections {
					type uint16 {
						range 1..4096;
					}
					must "current() <= 64 or (../client-list or ../mode[. = 'no-unauthenticated'])" {
						error-message "Disable unauthenticated mode or configure a client-list " +
									  "to enable more than 64 control sessions";
					}
					must "current() * ../maximum-sessions-per-connection <= 4096" {
						error-message "Maximum allowed test sessions must not exceed 4096";
					}
					default 16;
					configd:help "Maximum number of control sessions supported per TWAMP server, by default 16";
				}
				
				leaf maximum-sessions-per-connection {
					type session-num;
					default 8;
					configd:help "Maximum number of test sessions per control session, by default 8";
				}
				
				leaf server-inactivity-timeout {
					type timeout;
					default 900;
					configd:help "Control session inactivity timeout in seconds, by default 900";
				}
					
				leaf test-inactivity-timeout {
					type timeout;
					default 900;
					configd:help "Test session inactivity timeout in seconds, by default 900";
				}
				
				leaf port {
					type inet:port-number {
						range 1..65535;
					}
					default 862;
					configd:help "Server TCP port for control session, by default 862";
				}
					
				leaf dscp-value {
					type uint8 {
						range 0..63;
					}
					default 0;
					configd:help "Base 10 value of DSCP byte in IP header in control packets sent from server, by default 0";
				}

				leaf no-offload {
					type empty;
					configd:help "Disable support for dataplane processing of test frames";
				}
			}
		}
	}

	augment /service:service {
		uses twamp-parameters {
			refine twamp/server {
				configd:end "twampd-config.pl";
			}
		}
	}
}
